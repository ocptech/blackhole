module BLACKHOLE {

  namespace "http://example.com/BLACKHOLE";
  prefix BLACKHOLE;

  import ietf-inet-types {
    prefix inet;
  }
  import tailf-common {
    prefix tailf;
  }
  import tailf-ncs {
    prefix ncs;
  }

  list BLACKHOLE {
    description "This is an RFS skeleton service";

    key name;
    leaf name {
      tailf:info "Unique service id";
      tailf:cli-allow-range;
      type string;
    }

    uses ncs:service-data;
    ncs:servicepoint BLACKHOLE-servicepoint;


  }
}
